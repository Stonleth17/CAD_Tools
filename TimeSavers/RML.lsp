(defun c:rml ( / a i o s )
   (if (and (setq s (ssget "_:L" '((0 . "MULTILEADER"))))
            (setq a (getangle "\nSpecify rotation angle: "))
       )
       (repeat (setq i (sslength s))
           (setq i (1- i)
                 o (vlax-ename->vla-object (ssname s i))
           )
           (vla-rotate o (vlax-3D-point (mapcar '+ (vlax-invoke o 'getleaderlinevertices 0) '(0 0 0))) a)
       )
   )
   (princ)
)
(vl-load-com) (princ)
